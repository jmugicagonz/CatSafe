# gatera

## RF-G_01: El gato quiere salir de la vivienda (Functional)
| ID | RF-G_01 |
| --- | --- |
| XRref | 4.1 |
| Disparador | El gato se aproxima a la gatera desde el interior de la vivienda |
| Precondición | El gato se encuentra a una distancia corta de la gatera |
| Trayectoria usual | 1. El chip es detectado por el sensor de la gatera 2. Si el sistema está en modo manual, se envía un aviso en forma de notificación al dispositivo del usuario administrador de la presencia del gato. Se añade además dicha notificación a la pantalla de notificaciones con las opciones ‘abrir’ e ‘ignorar’. 3. Si el usuario administrador decide abrir la gatera, abrirá la App y en la pantalla de notificaciones pulsará sobre ‘abrir’. 4. Si el gato sale, será detectado por el sensor de detección de paso (identificando el gato que sale si varios gatos están registrados) en la gatera y el dueño será notificado de la salida del gato. Tras la salida del gato, la gatera se cerrará. |
| Trayectorias alternativas | En el paso 2, si la gatera está situada en modo automático, se abrirá directamente. 3) El usuario es notificado de la apertura de la gatera. 4) Si el gato sale, será detectado por el sensor de paso (identificando el gato que sale si varios gatos están registrados) en y el dueño será notificado de la salida del gato. Tras la salida del gato, la gatera se cerrará. En el paso 3, si el usuario decide no abrir la gatera, podrá ignorar el aviso o abrir la App y pulsará sobre el botón “ignorar”. Si decide ignorar el aviso, el sistema esperará un tiempo fijado por el usuario en la pantalla de menú, en la sección de parámetros del sistema, antes de enviar el siguiente aviso. En el paso 4, si el gato decide no salir, no será detectado por el sensor de detección de paso y el usuario no será notificado de la salida del gato. En ese caso la gatera se cerrará tras un tiempo fijado por el usuario en la pantalla de menú, en la sección de parámetros del sistema, si el gato no ha cruzado tras ese tiempo. |
| Postcondición | El gato sale de la vivienda o permanece en el interior, contabilizando en el registro de actividad correspondiente. La gatera se encuentra cerrada. |
| Excepciones | El gato puede alejarse de la gatera en cualquier momento del proceso. En ese caso la gatera se abrirá durante un tiempo fijado por el usuario en la sección de parámetros y se cerrará si el gato no ha cruzado tras ese tiempo. |
| Validación | Se realizarán tests con el gato aproximándose a la gatera desde el interior y se analizará el comportamiento de esta hasta cumplir las trayectorias previamente descritas. |
| Otros |  |

## RF-G_02: EL gato quiere entrar en la vivienda (Functional)
| Nombre del caso de uso | El gato quiere entrar a la vivienda |
| --- | --- |
| ID | RF-G_02 |
| XRref | 4.2 |
| Disparador | El gato se aproxima a la gatera desde el exterior de la vivienda |
| Precondición | El gato se encuentra a una distancia corta de la gatera |
| Trayectoria usual | 1. El chip es detectado por el sensor de la gatera 2. La gatera se abre. Se envía un aviso en forma de notificación al dispositivo del usuario administrador de la presencia del gato. Se añade la notificación en la pantalla de notificaciones. 3. El gato entra y es detectado por el sensor de paso (identificando el gato que sale si varios gatos están registrados). Se envía un aviso en forma de notificación al dueño de la entrada del gato. Se añade la notificación en la pantalla de notificaciones. 4. Se cierra la gatera. |
| Trayectorias alternativas | En el paso 3, el gato puede decidir no entrar y permanecer cerca de la gatera o alejarse de esta. En ese caso la gatera permanecerá abierta un tiempo fijado por el usuario y tras ese tiempo se cerrará. |
| Postcondición | El gato entra a la vivienda o permanece en el exterior, contabilizando en el registro de actividad correspondiente. La gatera se encuentra cerrada. |
| Excepciones |  |
| Validación | Se realizarán tests con el gato aproximándose a la gatera desde el exterior y se analizará el comportamiento de esta hasta cumplir las trayectorias previamente descritas. |
| Otros |  |

## RF-SY_01: Cambio de modo de uso de manual a automático (Functional)
| Nombre del caso de uso | Cambio del modo de uso del sistema |
| --- | --- |
| ID | RF-SY_01 |
| XRref | 4.3 |
| Disparador | El usuario administrador decide cambiar el modo de uso del sistema a modo automático |
| Precondición | El usuario administrador tiene abierta la App en la sección parámetros y el sistema está en modo manual. |
| Trayectoria usual | 1. El usuario decide cambiar al modo automático pulsando sobre el botón “automático”. 2. Se despliegan las horas a las que se alimentará al gato con el comedero. 3. El usuario selecciona las horas, pudiendo añadir o eliminar nuevos tiempos. 4. El usuario pulsa en guardar cambios. 5. Se añade a la pantalla de notificaciones el cambio a modo automático. |
| Trayectorias alternativas |  |
| Postcondición | La gatera y el comedero se sitúan en modo automático con las horas correspondientes para el comedero. |
| Excepciones | El usuario no guarda los cambios. En ese caso se conserva el modo manual previo. |
| Validación | Se hará un test en la App de cambio de modo a automático y se comprobará que se verifican la trayectoria usual y las excepciones. |
| Otros |  |

## RF-SY_02: Cambio de modo de automático a manual (Functional)
| Nombre del caso de uso | Cambio del modo de uso del sistema |
| --- | --- |
| ID | RF-SY_02 |
| XRref | 4.3 |
| Disparador | El usuario administrador decide cambiar el modo de uso del sistema |
| Precondición | El usuario administrador tiene abierta la App en la sección parámetros y el sistema está en modo manual. |
| Trayectoria usual | 1. El usuario decide cambiar al modo manual pulsando sobre el botón “manual”. 2. El usuario pulsa en guardar cambios. 3. Se añade a la pantalla de notificaciones el cambio a modo manual. |
| Trayectorias alternativas |  |
| Postcondición | La gatera y el comedero se sitúan en modo manual. |
| Excepciones | El usuario no guarda los cambios. En ese caso se conserva el modo automático previo con la configuración previa. |
| Validación | Se hará un test en la App de cambio de modo a manual y se comprobará que se verifican la trayectoria usual y las excepciones. |
| Otros |  |

## RF-CO_01: Alimentación del gato en modo manual (Functional)
| Nombre del caso de uso | Alimentación del gato en modo manual |
| --- | --- |
| ID | RF-CO_01 |
| XRref | 4.4 |
| Disparador | El usuario administrador decide alimentar al gato |
| Precondición | El usuario tiene la App en modo manual. |
| Trayectoria usual | 1. En la pantalla "menú", el dueño pulsa sobre manual. 2. El sistema despliega la pantalla correspondiente al modo manual. 2. El dueño pulsa sobre el botón que acciona el dispensador de comida. 3. El sistema dispensa comida. Se añade a la pantalla de notificaciones que se ha dispensado comida. |
| Trayectorias alternativas |  |
| Postcondición | El gato cuenta con comida en el comedero. |
| Excepciones | El Sistema se ha quedado sin comida y no puede dispensar. En este caso, el dueño no sabrá si no queda comida restante, por lo que deberá haber calculado con anterioridad la comida suficiente para alimentar a la mascota el tiempo que esté fuera. |
| Validación | Se realizará un test en el que se seguirán los pasos descritos en la trayectoria usual y se comprobará que efectivamente se dispensa comida. |
| Otros |  |

## RF-CO_02: Alimentación del gato en modo automático (Functional)
| Nombre del caso de uso | Alimentación del gato en modo automático |
| --- | --- |
| ID | RF-CO_02 |
| XRref | 4.4 |
| Disparador | Se dispensa comida en el comedero en las horas programadas por el usuario |
| Precondición | El dueño tiene la App en modo automático |
| Trayectoria usual | 1. Llega la hora seleccionada por el usuario. 2. El sistema dispensa comida. 3. Se añade a la pantalla de notificaciones que se ha dispensado comida. |
| Trayectorias alternativas |  |
| Postcondición | El gato cuenta con comida en el comedero. |
| Excepciones | El Sistema se ha quedado sin comida y no puede dispensar. En este caso, el dueño no sabrá si no queda comida restante, por lo que deberá haber calculado con anterioridad la comida suficiente para alimentar a la mascota el tiempo que esté fuera. |
| Validación | Se realizará un test en el que se seguirán los pasos descritos en la trayectoria usual y se comprobará que efectivamente se dispensa comida. |
| Otros |  |

## RNF-SE_01: Parada de Emergencia (Functional)
| ID | Título | Descripción | Validación |
| --- | --- | --- | --- |
| RNF-SE_01 | Parada de Emergencia | El sistema debe ser capaz de ejecutar una parada de emergencia cuando se detecte algún malfuncionamiento | Se activará la función de parada cuando haya algún malfuncionamiento del sistema. A continuación, el sistema se bloqueará instantáneamente, hasta que el usuario indique lo contrario |

## RF-SY_04: El dueño quiere ver el registro de actividad del gato (Functional)
| Nombre del caso de uso | El dueño quiere ver el registro de actividad del gato |
| --- | --- |
| ID | RF-SY_04 |
| XRref | 4.6 |
| Disparador | El dueño decide mirar el registro de actividad del gato. |
| Precondición | El dueño tiene abierta la App. |
| Trayectoria usual | 1. El usuario administrador accede a la pantalla de actividad. 2. En esta pantalla puede observar los datos correspondientes a los registros de actividad del gato así como gráficas obtenidas a partir de ellos (para una mejor visualización). |
| Trayectorias alternativas |  |
| Postcondición | El dueño ha podido observar el registro de actividad del gato. |
| Excepciones |  |
| Validación | Se harán varios tests en los que el gato estará dentro o fuera de la vivienda, pasando a través de la gatera para cambiar de estado, y se comprobará que la información mostrada en la pantalla de actividad es real. |
| Otros |  |

## RF-SY_05: El dueño quiere introducir un nuevo gato en el sistema (Functional)
| Nombre del caso de uso | El dueño quiere introducir un nuevo gato en el sistema |
| --- | --- |
| ID | RF-SY_05 |
| XRref | 4.8 |
| Disparador | El dueño decide añadir una mascota al sistema |
| Precondición | El usuario ha colocado en el collar de la mascota un chip compatible con el sensor de proximidad situado en la gatera. |
| Trayectoria usual | 1. El usuario abre la App y pulsa sobre la pantalla menú. 2. En la pantalla de menú, pulsa sobre la opción de añadir mascota. 3. El sistema muestra un listado de instrucciones para sincronizar el chip al sensor de detección de presencia de la gatera. 4. El sistema muestra un listado de instrucciones para sincronizar el chip identificador interno del gato al sensor de paso de la gatera. 5. Se añade a la pantalla de notificaciones la correspondiente adición de la mascota al sistema. |
| Trayectorias alternativas |  |
| Postcondición | El nuevo gato se encuentra registrado en el sistema. |
| Excepciones |  |
| Validación | Se realizarán tests en los que se seguirá la trayectoria usual descrita y se comprobará que la mascota se añade correctamente al sistema. |
| Otros |  |

## RF-CA_01: El dueño quiere ver las imágenes de las cámaras a tiempo real (Functional)
| Nombre del caso de uso | El dueño quiere observar al gato |
| --- | --- |
| ID | RF-CA_01 |
| XRref | 4.7 |
| Disparador | El dueño quiere ver las imágenes de las cámaras a tiempo real |
| Precondición | El dueño tiene la App abierta |
| Trayectoria usual | 1. El dueño accede a la pantalla de cámaras en la App. 2. El sistema abre la pantalla de cámaras y muestra una lista de las cámaras que se pueden visualizar. 3. El dueño elige la cámara que desea visualizar y pulsa sobre ella. 4. El sistema muestra a tiempo real las imágenes de dicha cámara. |
| Trayectorias alternativas |  |
| Postcondición | El dueño ha podido observar las cámaras de vigilancia. |
| Excepciones |  |
| Validación | Se realizarán tests siguiendo la trayectoria usual hasta lograr visualizar las imágenes de las diferentes cámaras conectadas al sistema. |
| Otros |  |

## RF-SY_06: Aviso de emergencia. El gato lleva demasiado tiempo en el exterior (Functional)
| Nombre del caso de uso | Aviso de emergencia. El gato lleva demasiado tiempo en el exterior |
| --- | --- |
| ID | RF-SY_06 |
| XRref | 4.9 |
| Disparador | El Sistema detecta que la mascota lleva más tiempo en el exterior que el fijado como el usuario administrador como tiempo límite en el exterior. |
| Precondición | El usuario ha fijado un tiempo límite en el exterior en la pantalla de menú, en la sección de parámetros. |
| Trayectoria usual | 1. El tiempo de estancia en el exterior de la mascota supera el tiempo límite fijado por el usuario administrador. 2. El sistema envía una notificación al móvil del usuario informándole de la situación. El sistema añade la notificación en la pantalla de notificaciones. |
| Trayectorias alternativas |  |
| Postcondición | El usuario se encuentra al tanto de la situación. |
| Excepciones |  |
| Validación | Se realizarán tests en los que la mascota exceda dicho tiempo límite en el exterior y se comprobará que se envía de forma correcta la notificación y que esta se añade a la pantalla de notificaciones. |
| Otros |  |

## RF-SY_08 (Requisito cruzado): Aviso de emergencia. Aviso de Lluvia (Functional)
| Nombre del caso de uso | Aviso de emergencia. Aviso de Lluvia |
| --- | --- |
| XRref | 4.11 |
| ID | RF-SY_08 (Requisito cruzado) |
| Disparador | El servidor recibe un aviso de lluvia por parte del Sistema de Huerto Domotizado. |
| Precondición |  |
| Trayectoria usual | 1. El servidor recibe un aviso de lluvia. 2. El sistema envía una notificación al móvil del usuario informándole de la situación. El sistema añade la notificación en la pantalla de notificaciones. |
| Trayectorias alternativas |  |
| Postcondición | El dueño se encuentra al tanto de la situación. |
| Excepciones |  |
| Validación | Se realizarán test en los que se envía al servidor el aviso de lluvia y se comprobará que se envía de forma correcta la notificación y que esta se añade a la pantalla de notificaciones. |
| Otros |  |

## RF-SY_07 (Requisito cruzado): Aviso de emergencia. El gato lleva demasiado tiempo sin alimentarse (Functional)
| Nombre del caso de uso | Aviso de emergencia. El gato lleva demasiado tiempo sin alimentarse |
| --- | --- |
| XRref | 4.10 |
| ID | RF-SY_07 (Requisito cruzado) |
| Disparador | El Sistema detecta que el tiempo sin dispensar comida a superado el fijado por el usuario administrador como tiempo límite sin dispensar comida. |
| Precondición | 1. El usuario ha fijado un tiempo límite sin dispensar comida en la pantalla de menú, en la sección de parámetros. 2. El sistema está en modo manual |
| Trayectoria usual | 1. El tiempo sin dispensar comida supera el tiempo límite fijado por el usuario administrador. 2. El sistema envía una notificación al móvil del usuario informándole de la situación. El sistema añade la notificación en la pantalla de notificaciones. |
| Trayectorias alternativas | En el paso 2, si los datos del Sistema de Calidad del Sueño indican que el dueño se encuentra durmiendo: 2. El sistema dispensador dispensa comida automáticamente. |
| Postcondición | Si el dueño se encuentra dormido, la comida se habrá dispensado automáticamente. En el otro caso (dueño despierto), el resultado dependerá de la decisión del dueño. |
| Excepciones | Si el Sistema está en modo automático y el espacio entre tiempos de dispensar comida supera el tiempo límite fijado por el usuario, se informará a este de que debe modificar o las horas fijadas o el tiempo límite definido para que exista coherencia. |
| Validación | Se realizarán tests en los que se exceda dicho tiempo sin dispensar comida y se comprobará que se envía de forma correcta la notificación y que esta se añade a la pantalla de notificaciones. También se testeará que se cumple la excepción en modo automático. |
| Otros |  |
